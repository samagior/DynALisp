(defun c:la-A (/ _lay _msg) 
    (setq _lay "A-*,A?-*"
          _msg "Architectural"
    )
    (layadd _lay _msg)
)
(defun c:la-C (/ _lay _msg) 
    (setq _lay "C-*,C?-*"
          _msg "Civil"
    )
    (layadd _lay _msg)
)
(defun c:la-Z (/ _lay _msg) 
    (setq _lay "Z-*,Z?-*"
          _msg "Contractor"
    )
    (layadd _lay _msg)
)
(defun c:la-E (/ _lay _msg) 
    (setq _lay "E-*,E?-*"
          _msg "Electrical"
    )
    (layadd _lay _msg)
)
(defun c:la-W (/ _lay _msg) 
    (setq _lay "W-*,W?-*"
          _msg "Energy"
    )
    (layadd _lay _msg)
)
(defun c:la-Q (/ _lay _msg) 
    (setq _lay "Q-*,Q?-*"
          _msg "Equipment"
    )
    (layadd _lay _msg)
)
(defun c:la-F (/ _lay _msg) 
    (setq _lay "F-*,F?-*"
          _msg "Fire Protection"
    )
    (layadd _lay _msg)
)
(defun c:la-G (/ _lay _msg) 
    (setq _lay "G-*,G?-*"
          _msg "General"
    )
    (layadd _lay _msg)
)
(defun c:la-B (/ _lay _msg) 
    (setq _lay "B-*,B?-*"
          _msg "Geotechnical"
    )
    (layadd _lay _msg)
)
(defun c:la-H (/ _lay _msg) 
    (setq _lay "H-*,H?-*"
          _msg "Hazardeous Materials"
    )
    (layadd _lay _msg)
)
(defun c:la-I (/ _lay _msg) 
    (setq _lay "I-*,I?-*"
          _msg "Interior"
    )
    (layadd _lay _msg)
)
(defun c:la-L (/ _lay _msg) 
    (setq _lay "L-*,L?-*"
          _msg "Landscape"
    )
    (layadd _lay _msg)
)
(defun c:la-M (/ _lay _msg) 
    (setq _lay "M-*,M?-*"
          _msg "Mechanical"
    )
    (layadd _lay _msg)
)
(defun c:la-O (/ _lay _msg) 
    (setq _lay "O-*,O?-*"
          _msg "Operation"
    )
    (layadd _lay _msg)
)
(defun c:la-X (/ _lay _msg) 
    (setq _lay "X-*,X?-*"
          _msg "Other User Defined Discipline"
    )
    (layadd _lay _msg)
)
(defun c:la-P (/ _lay _msg) 
    (setq _lay "P-*,P?-*"
          _msg "Plumbing"
    )
    (layadd _lay _msg)
)
(defun c:la-D (/ _lay _msg) 
    (setq _lay "D-*,D?-*"
          _msg "Process"
    )
    (layadd _lay _msg)
)
(defun c:la-R (/ _lay _msg) 
    (setq _lay "R-*,R?-*"
          _msg "Resource"
    )
    (layadd _lay _msg)
)
(defun c:la-S (/ _lay _msg) 
    (setq _lay "S-*,S?-*"
          _msg "Structural"
    )
    (layadd _lay _msg)
)
(defun c:la-V (/ _lay _msg) 
    (setq _lay "V-*,V?-*"
          _msg "Survey"
    )
    (layadd _lay _msg)
)
(defun c:la-T (/ _lay _msg) 
    (setq _lay "T-*,T?-*"
          _msg "Telecom"
    )
    (layadd _lay _msg)
)
