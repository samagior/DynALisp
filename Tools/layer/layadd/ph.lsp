(defun c:la-1 (/ _lay _msg) 
    (setq _lay "*-1"
          _msg "Phase 1"
    )
    (layadd _lay _msg)
)
(defun c:la-2 (/ _lay _msg) 
    (setq _lay "*-2"
          _msg "Phase 2"
    )
    (layadd _lay _msg)
)
(defun c:la-3 (/ _lay _msg) 
    (setq _lay "*-3"
          _msg "Phase 3"
    )
    (layadd _lay _msg)
)
(defun c:la-4 (/ _lay _msg) 
    (setq _lay "*-4"
          _msg "Phase 4"
    )
    (layadd _lay _msg)
)
(defun c:la-5 (/ _lay _msg) 
    (setq _lay "*-5"
          _msg "Phase 5"
    )
    (layadd _lay _msg)
)
(defun c:la-6 (/ _lay _msg) 
    (setq _lay "*-6"
          _msg "Phase 6"
    )
    (layadd _lay _msg)
)
(defun c:la-7 (/ _lay _msg) 
    (setq _lay "*-7"
          _msg "Phase 7"
    )
    (layadd _lay _msg)
)
(defun c:la-8 (/ _lay _msg) 
    (setq _lay "*-8"
          _msg "Phase 8"
    )
    (layadd _lay _msg)
)
(defun c:la-9 (/ _lay _msg) 
    (setq _lay "*-9"
          _msg "Phase 9"
    )
    (layadd _lay _msg)
)
(defun c:la-Neww (/ _lay _msg) 
    (setq _lay "*-N"
          _msg "New Work"
    )
    (layadd _lay _msg)
)
(defun c:la-Exst (/ _lay _msg) 
    (setq _lay "*-E"
          _msg "Existing to remain"
    )
    (layadd _lay _msg)
)
(defun c:la-Demo (/ _lay _msg) 
    (setq _lay "*-D"
          _msg "Existing to Demolish"
    )
    (layadd _lay _msg)
)
(defun c:la-Move (/ _lay _msg) 
    (setq _lay "*-M"
          _msg "Item to be Moved"
    )
    (layadd _lay _msg)
)
(defun c:la-Abnd (/ _lay _msg) 
    (setq _lay "*-A"
          _msg "Abandonned"
    )
    (layadd _lay _msg)
)
(defun c:la-Rfsh (/ _lay _msg) 
    (setq _lay "*-R"
          _msg "Refurbished"
    )
    (layadd _lay _msg)
)
(defun c:la-Temp (/ _lay _msg) 
    (setq _lay "*-T"
          _msg "Temporary"
    )
    (layadd _lay _msg)
)
(defun c:la-Prow (/ _lay _msg) 
    (setq _lay "*-P"
          _msg "Proposed Work"
    )
    (layadd _lay _msg)
)
(defun c:la-Futw (/ _lay _msg) 
    (setq _lay "*-F"
          _msg "Futur Work"
    )
    (layadd _lay _msg)
)
(defun c:la-Save (/ _lay _msg) 
    (setq _lay "*-S"
          _msg "Existing to be Saved"
    )
    (layadd _lay _msg)
)
