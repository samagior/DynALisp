(defun c:la-Anno (/ _lay _msg) 
    (setq _lay "*Anno*,*Labl*,*Tags*,*Note*,*Text*,*Iden*,*Revc*,*Refr*,*Symb*,*Dims*,*Grid*"
          _msg "Annotations"
    )
    (layadd _lay _msg)
)
(defun c:la-Patt (/ _lay _msg) 
    (setq _lay "*Patt*"
          _msg "Hatch Patterns"
    )
    (layadd _lay _msg)
)
(defun c:la-Labl (/ _lay _msg) 
    (setq _lay "*Labl*"
          _msg "Labels"
    )
    (layadd _lay _msg)
)
(defun c:la-Tags (/ _lay _msg) 
    (setq _lay "*Tags*"
          _msg "Tags"
    )
    (layadd _lay _msg)
)
(defun c:la-Note (/ _lay _msg) 
    (setq _lay "*Note*"
          _msg "Notes"
    )
    (layadd _lay _msg)
)
(defun c:la-Text (/ _lay _msg) 
    (setq _lay "*Text*"
          _msg "Texts"
    )
    (layadd _lay _msg)
)
(defun c:la-Iden (/ _lay _msg) 
    (setq _lay "*Iden*"
          _msg "Identifications"
    )
    (layadd _lay _msg)
)
(defun c:la-Revc (/ _lay _msg) 
    (setq _lay "*Revc*"
          _msg "Revision Clouds"
    )
    (layadd _lay _msg)
)
(defun c:la-Refr (/ _lay _msg) 
    (setq _lay "*Refr*"
          _msg "External reference files"
    )
    (layadd _lay _msg)
)
(defun c:la-Scrn (/ _lay _msg) 
    (setq _lay "*Scrn*"
          _msg "Backgroud Screening"
    )
    (layadd _lay _msg)
)
(defun c:la-Symb (/ _lay _msg) 
    (setq _lay "*Symb*"
          _msg "Symbols"
    )
    (layadd _lay _msg)
)
(defun c:la-Dims (/ _lay _msg) 
    (setq _lay "*Dims*"
          _msg "Dimensions"
    )
    (layadd _lay _msg)
)
(defun c:la-Grid (/ _lay _msg) 
    (setq _lay "*Grid*"
          _msg "Grids"
    )
    (layadd _lay _msg)
)
(defun c:la-Mask (/ _lay _msg) 
    (setq _lay "*Mask*"
          _msg "Masking Objects"
    )
    (layadd _lay _msg)
)
(defun c:la-Nplt (/ _lay _msg) 
    (setq _lay "*Nplt*"
          _msg "Non-plottable reference lines"
    )
    (layadd _lay _msg)
)
(defun c:la-0001 (/ _lay _msg) 
    (setq _lay "*0001*"
          _msg "Stack Number 1"
    )
    (layadd _lay _msg)
)
(defun c:la-0002 (/ _lay _msg) 
    (setq _lay "*0002*"
          _msg "Stack Number 2"
    )
    (layadd _lay _msg)
)
(defun c:la-0003 (/ _lay _msg) 
    (setq _lay "*0003*"
          _msg "Stack Number 3"
    )
    (layadd _lay _msg)
)
(defun c:la-0004 (/ _lay _msg) 
    (setq _lay "*0004*"
          _msg "Stack Number 4"
    )
    (layadd _lay _msg)
)
(defun c:la-0005 (/ _lay _msg) 
    (setq _lay "*0005*"
          _msg "Stack Number 5"
    )
    (layadd _lay _msg)
)
(defun c:la-0006 (/ _lay _msg) 
    (setq _lay "*0006*"
          _msg "Stack Number 6"
    )
    (layadd _lay _msg)
)
(defun c:la-0007 (/ _lay _msg) 
    (setq _lay "*0007*"
          _msg "Stack Number 7"
    )
    (layadd _lay _msg)
)
(defun c:la-0008 (/ _lay _msg) 
    (setq _lay "*0008*"
          _msg "Stack Number 8"
    )
    (layadd _lay _msg)
)
(defun c:la-0009 (/ _lay _msg) 
    (setq _lay "*0009*"
          _msg "Stack Number 9"
    )
    (layadd _lay _msg)
)
