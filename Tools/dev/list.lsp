(defun c:entlist (/ ent ctr) 
    (setq ent (entget (car (entsel)))
          ctr 0
    )
    (textpage)
    (repeat (length ent) 
        (print (nth ctr ent))
        (setq ctr (1+ ctr))
    )
    (princ)
)

(defun c:arxlist (/ acadObj appList I) 
    (vl-load-com)
    (setq acadObj (vlax-get-acad-object))
    (setq appList (vla-ListArx acadObj))
    (if (/= (vlax-variant-value appList) vlax-vbEmpty) 
        (progn 
            (setq I       0
                  appList (vlax-variant-value appList)
            )
            (while (>= (vlax-safearray-get-u-bound appList 1) I) 
                (princ (strcat "\n" (vlax-safearray-get-element appList I)))
                (setq I (1+ I))
            )
        )
        (alert "No ObjectARX applications loaded.")
    )
)
