(defun c:lts-reset (/ ss i) 
    (alert "Resetting all linetypes scale to 1.0")
    (if (setq ss (ssget "_X" '((0 . "LINE,*POLYLINE")))) 
        (repeat (setq i (sslength ss)) 
            (entmod (append (entget (ssname ss (setq i (1- i)))) '((48 . 1.))))
        )
    )
    (princ)
)
